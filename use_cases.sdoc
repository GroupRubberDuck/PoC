[DOCUMENT]
TITLE: Use Cases

[REQUIREMENT]
UID: UC01
TITLE: UC01 - Visualizza lista dispositivi

[REQUIREMENT]
UID: UC01.1
TITLE: UC01.1 - Visualizza elemento lista dispositivi

[REQUIREMENT]
UID: UC01.1.1
TITLE: UC01.1.1 - Visualizza nome dispositivo su lista dispositivi

[REQUIREMENT]
UID: UC02
TITLE: UC02 - Inserimento nuovo dispositivo

[REQUIREMENT]
UID: UC03
TITLE: UC03 - Annullamento inserimento dispositivo

[REQUIREMENT]
UID: UC04
TITLE: UC04 - Crea nuovo dispositivo

[REQUIREMENT]
UID: UC04.1
TITLE: UC04.1 - Inserimento nome dispositivo

[REQUIREMENT]
UID: UC04.1.1
TITLE: UC04.1.1 - Errore nome dispositivo non valido

[REQUIREMENT]
UID: UC04.2
TITLE: UC04.2 - Inserimento sistema operativo dispositivo

[REQUIREMENT]
UID: UC04.3
TITLE: UC04.3 - Inserimento descrizione dispositivo

[REQUIREMENT]
UID: UC05
TITLE: UC05 - Importa dispositivo

[REQUIREMENT]
UID: UC05.1
TITLE: UC05.1 - Selezione file sorgente

[REQUIREMENT]
UID: UC05.1.1
TITLE: UC05.1.1 - Selezione file JSON

[REQUIREMENT]
UID: UC05.1.2
TITLE: UC05.1.2 - Selezione file XML

[REQUIREMENT]
UID: UC05.1.3
TITLE: UC05.1.3 - Selezione file CSV

[REQUIREMENT]
UID: UC06
TITLE: UC06 - Errore file dispositivo non valido (Implementato)

[REQUIREMENT]
UID: UC07
TITLE: UC07 - Visualizza dati dispositivo

[REQUIREMENT]
UID: UC07.1
TITLE: UC07.1 - Visualizza nome dispositivo

[REQUIREMENT]
UID: UC07.2
TITLE: UC07.2 - Visualizza sistema operativo dispositivo

[REQUIREMENT]
UID: UC07.3
TITLE: UC07.3 - Visualizza descrizione dispositivo

[REQUIREMENT]
UID: UC07.4
TITLE: UC07.4 - Visualizza modello associato al dispositivo

[REQUIREMENT]
UID: UC07.4.1
TITLE: UC07.4.1 - Visualizza nome modello associato

[REQUIREMENT]
UID: UC07.4.2
TITLE: UC07.4.2 - Visualizza versione modello associato

[REQUIREMENT]
UID: UC08
TITLE: UC08 - Modifica dispositivo

[REQUIREMENT]
UID: UC08.1
TITLE: UC08.1 - Modifica nome dispositivo

[REQUIREMENT]
UID: UC08.1.1
TITLE: UC08.1.1 - Errore modifica nome dispositivo non valido

[REQUIREMENT]
UID: UC08.2
TITLE: UC08.2 - Modifica sistema operativo dispositivo

[REQUIREMENT]
UID: UC08.3
TITLE: UC08.3 - Modifica descrizione dispositivo

[REQUIREMENT]
UID: UC08.4
TITLE: UC08.4 - Annulla modifiche dispositivo

[REQUIREMENT]
UID: UC09
TITLE: UC09 - Elimina dispositivo

[REQUIREMENT]
UID: UC09.1
TITLE: UC09.1 - Elimina dispositivo direttamente

[REQUIREMENT]
UID: UC09.2
TITLE: UC09.2 - Elimina dispositivo con back up

[REQUIREMENT]
UID: UC09.2.1
TITLE: UC09.2.1 - Elimina dispositivo con back up JSON

[REQUIREMENT]
UID: UC09.2.2
TITLE: UC09.2.2 - Elimina dispositivo con back up XML

[REQUIREMENT]
UID: UC09.2.3
TITLE: UC09.2.3 - Elimina dispositivo con back up CSV

[REQUIREMENT]
UID: UC10
TITLE: UC10 - Avvia valutazione dispositivo

[REQUIREMENT]
UID: UC11
TITLE: UC11 - Scarta modifiche valutazione

[REQUIREMENT]
UID: UC12
TITLE: UC12 - Salva valutazione

[REQUIREMENT]
UID: UC12.1
TITLE: UC12.1 - Salva e chiudi valutazione dispositivo

[REQUIREMENT]
UID: UC12.2
TITLE: UC12.2 - Salva e continua valutazione dispositivo

[REQUIREMENT]
UID: UC13
TITLE: UC13 - Errore salvataggio valutazione

[REQUIREMENT]
UID: UC14
TITLE: UC14 - Aggiunta asset

[REQUIREMENT]
UID: UC14.1
TITLE: UC14.1 - Inserisci nome asset

[REQUIREMENT]
UID: UC14.1.1
TITLE: UC14.1.1 - Errore nome asset non valido

[REQUIREMENT]
UID: UC14.2
TITLE: UC14.2 - Seleziona tipo asset

[REQUIREMENT]
UID: UC14.2.1
TITLE: UC14.2.1 - Seleziona security asset

[REQUIREMENT]
UID: UC14.2.2
TITLE: UC14.2.2 - Seleziona network asset

[REQUIREMENT]
UID: UC14.3
TITLE: UC14.3 - Inserisci descrizione asset

[REQUIREMENT]
UID: UC15
TITLE: UC15 - Annulla aggiunta asset

[REQUIREMENT]
UID: UC16
TITLE: UC16 - Visualizza dashboard dispositivo

[REQUIREMENT]
UID: UC16.1
TITLE: UC16.1 - Visualizza dati dispositivo su dashboard

[REQUIREMENT]
UID: UC16.1.1
TITLE: UC16.1.1 - Visualizza nome dispositivo su dashboard

[REQUIREMENT]
UID: UC16.1.2
TITLE: UC16.1.2 - Visualizza sistema operativo dispositivo su dashboard

[REQUIREMENT]
UID: UC16.1.3
TITLE: UC16.1.3 - Visualizza descrizione dispositivo su dashboard

[REQUIREMENT]
UID: UC16.2
TITLE: UC16.2 - Visualizza stato aggregato dispositivo

[REQUIREMENT]
UID: UC16.3
TITLE: UC16.3 - Visualizza lista asset

[REQUIREMENT]
UID: UC16.3.1
TITLE: UC16.3.1 - Visualizza singolo elemento lista asset

[REQUIREMENT]
UID: UC17.1
TITLE: UC17.1 - Visualizza nome asset

[REQUIREMENT]
UID: UC17.2
TITLE: UC17.2 - Visualizza tipo asset

[REQUIREMENT]
UID: UC17.3
TITLE: UC17.3 - Visualizza stato aggregato asset

[REQUIREMENT]
UID: UC17.4
TITLE: UC17.4 - Visualizza descrizione asset

[REQUIREMENT]
UID: UC17.5
TITLE: UC17.5 - Visualizza lista requisiti asset

[REQUIREMENT]
UID: UC17.5.1
TITLE: UC17.5.1 - Visualizza elemento lista requisiti asset

[REQUIREMENT]
UID: UC17.5.1.1
TITLE: UC17.5.1.1 - Visualizza codice requisito da lista requisiti

[REQUIREMENT]
UID: UC17.5.1.2
TITLE: UC17.5.1.2 - Visualizza stato valutazione requisito da lista requisiti

[REQUIREMENT]
UID: UC18
TITLE: UC18 - Elimina asset

[REQUIREMENT]
UID: UC19
TITLE: UC19 - Modifica asset

[REQUIREMENT]
UID: UC19.1
TITLE: UC19.1 - Modifica nome asset

[REQUIREMENT]
UID: UC19.1.1
TITLE: UC19.1.1 - Errore modifica nome asset non valido

[REQUIREMENT]
UID: UC19.2
TITLE: UC19.2 - Modifica tipo asset

[REQUIREMENT]
UID: UC19.2.1
TITLE: UC19.2.1 - Seleziona nuovo tipo security asset

[REQUIREMENT]
UID: UC19.2.2
TITLE: UC19.2.2 - Seleziona nuovo tipo network asset

[REQUIREMENT]
UID: UC19.3
TITLE: UC19.3 - Modifica descrizione asset  

[REQUIREMENT]
UID: UC20
TITLE: UC20 - Annulla modifica asset

[REQUIREMENT]
UID: UC21
TITLE: UC21 - Esporta informazioni dispositivo

[REQUIREMENT]
UID: UC21.1
TITLE: UC21.1 - Esporta in XML

[REQUIREMENT]
UID: UC21.2
TITLE: UC21.2 - Esporta in JSON 

[REQUIREMENT]
UID: UC21.3
TITLE: UC21.3 - Esporta in CSV

[REQUIREMENT]
UID: UC22
TITLE: UC22 - Visualizza dettaglio requisito

[REQUIREMENT]
UID: UC22.1
TITLE: UC22.1 - Visualizza codice requisito

[REQUIREMENT]
UID: UC22.2
TITLE: UC22.2 - Visualizza nome del requisito

[REQUIREMENT]
UID: UC22.3
TITLE: UC22.3 - Visualizza descrizione normativa

[REQUIREMENT]
UID: UC22.4
TITLE: UC22.4 - Visualizza stato valutazione requisito

[REQUIREMENT]
UID: UC22.4.1
TITLE: UC22.4.1 - Visualizza stato pass requisito

[REQUIREMENT]
UID: UC22.4.2
TITLE: UC22.4.2 - Visualizza stato fail requisito

[REQUIREMENT]
UID: UC22.4.3
TITLE: UC22.4.3 - Visualizza stato na requisito

[REQUIREMENT]
UID: UC22.4.4
TITLE: UC22.4.4 - Visualizza stato in corso requisito

[REQUIREMENT]
UID: UC22.4.5
TITLE: UC22.4.5 - Visualizza stato sospeso requisito

[REQUIREMENT]
UID: UC22.5
TITLE: UC22.5 - Visualizza lista dipendenze requisito

[REQUIREMENT]
UID: UC22.5.1
TITLE: UC22.5.1 - Visualizza sintesi dipendenza

[REQUIREMENT]
UID: UC22.5.1.1
TITLE: UC22.5.1.1 - Visualizza codice dipendenza

[REQUIREMENT]
UID: UC22.5.1.2
TITLE: UC22.5.1.2 - Visualizza stato dipendenza

[REQUIREMENT]
UID: UC22.6
TITLE: UC22.6 - Visualizza decision tree

[REQUIREMENT]
UID: UC22.6.1
TITLE: UC22.6.1 - Visualizza nodo decision tree

[REQUIREMENT]
UID: UC22.6.1.1
TITLE: UC22.6.1.1 - Visualizza stato attività

[REQUIREMENT]
UID: UC22.6.2
TITLE: UC22.6.2 - Visualizza nodo di decisione

[REQUIREMENT]
UID: UC22.6.2.1
TITLE: UC22.6.2.1 - Visualizza codice requisito DT

[REQUIREMENT]
UID: UC22.6.2.2
TITLE: UC22.6.2.2 - Visualizza codice nodo

[REQUIREMENT]
UID: UC22.6.2.3
TITLE: UC22.6.2.3 - Visualizza domanda nodo

[REQUIREMENT]
UID: UC22.6.2.4
TITLE: UC22.6.2.4 - Visualizza risposta nodo

[REQUIREMENT]
UID: UC22.6.2.4.1
TITLE: UC22.6.2.4.1 - Nessuna risposta associata

[REQUIREMENT]
UID: UC22.6.3
TITLE: UC22.6.3 - Visualizza nodo foglia

[REQUIREMENT]
UID: UC22.6.3.1
TITLE: UC22.6.3.1 - Visualizza valore nodo foglia

[REQUIREMENT]
UID: UC22.7
TITLE: UC22.7 - Visualizza giustificazione decision tree

[REQUIREMENT]
UID: UC23
TITLE: UC23 - Visualizza dettaglio nodo decisionale

[REQUIREMENT]
UID: UC23.1
TITLE: UC23.1 - Visualizza codice requisito a dettaglio

[REQUIREMENT]
UID: UC23.2
TITLE: UC23.2 - Visualizza codice nodo a dettaglio

[REQUIREMENT]
UID: UC23.3
TITLE: UC23.3 - Visualizza domanda nodo a dettaglio

[REQUIREMENT]
UID: UC23.4
TITLE: UC23.4 - Visualizza risposta nodo a dettaglio

[REQUIREMENT]
UID: UC23.4.1
TITLE: UC23.4.1 - Mostra assenza di risposta a dettaglio

[REQUIREMENT]
UID: UC24
TITLE: UC24 - Valuta nodo di decisione

[REQUIREMENT]
UID: UC24.1
TITLE: UC24.1 - Inserisci risposta nodo decision tree

[REQUIREMENT]
UID: UC24.1.1
TITLE: UC24.1.1 - Seleziona yes

[REQUIREMENT]
UID: UC24.1.2
TITLE: UC24.1.2 - Seleziona no

[REQUIREMENT]
UID: UC25
TITLE: UC25 - Vai al nodo successivo

[REQUIREMENT]
UID: UC25.1
TITLE: UC25.1 - Nodo senza risposta selezionata

[REQUIREMENT]
UID: UC25.2
TITLE: UC25.2 - Nodo successore foglia

[REQUIREMENT]
UID: UC26
TITLE: UC26 - Vai al nodo precedente

[REQUIREMENT]
UID: UC26.1
TITLE: UC26.1 - Nodo corrente root

[REQUIREMENT]
UID: UC27
TITLE: UC27 - Inserisci giustificazione decision tree

[REQUIREMENT]
UID: UC28
TITLE: UC28 - Esporta report di conformità

[REQUIREMENT]
UID: UC28.1
TITLE: UC28.1 - Esporta report in pdf

[REQUIREMENT]
UID: UC29
TITLE: UC29 - Visualizza lista modelli

[REQUIREMENT]
UID: UC29.1
TITLE: UC29.1 - Visualizza elemento lista modelli

[REQUIREMENT]
UID: UC29.1.1
TITLE: UC29.1.1 - Visualizza nome modello da lista modelli

[REQUIREMENT]
UID: UC29.1.2
TITLE: UC29.1.2 - Visualizza versione modello da lista modelli

[REQUIREMENT]
UID: UC30
TITLE: UC30 - Visualizza dettaglio modello

[REQUIREMENT]
UID: UC30.1
TITLE: UC30.1 - Visualizza id modello

[REQUIREMENT]
UID: UC30.2
TITLE: UC30.2 - Visualizza nome modello

[REQUIREMENT]
UID: UC30.3
TITLE: UC30.3 - Visualizza versione modello

[REQUIREMENT]
UID: UC30.4
TITLE: UC30.4 - Visualizza lista requisiti modello

[REQUIREMENT]
UID: UC30.4.1
TITLE: UC30.4.1 - Visualizza singolo elemento lista requisiti modello

[REQUIREMENT]
UID: UC30.4.1.1
TITLE: UC30.4.1.1 - Visualizza codice requisito da lista requisiti modello

[REQUIREMENT]
UID: UC30.4.1.2
TITLE: UC30.4.1.2 - Visualizza nome requisito da lista requisiti modello

[REQUIREMENT]
UID: UC31
TITLE: UC31 - Inserisci nuovo modello

[REQUIREMENT]
UID: UC31.1
TITLE: UC31.1 - Crea nuovo modello

[REQUIREMENT]
UID: UC31.1.1
TITLE: UC31.1.1 - Inserisci nome modello

[REQUIREMENT]
UID: UC31.1.1.1
TITLE: UC31.1.1.1 - Errore nome nuovo modello non valido

[REQUIREMENT]
UID: UC31.2
TITLE: UC31.2 - Importa nuovo modello

[REQUIREMENT]
UID: UC31.2.1
TITLE: UC31.2.1 - Errore modello esistente

[REQUIREMENT]
UID: UC31.3
TITLE: UC31.3 - Importa modello file XML

[REQUIREMENT]
UID: UC31.4
TITLE: UC31.4 - Importa modello file JSON

[REQUIREMENT]
UID: UC32
TITLE: UC32 - Annulla inserimento modello

[REQUIREMENT]
UID: UC33
TITLE: UC33 - Modifica anagrafica modello

[REQUIREMENT]
UID: UC33.1
TITLE: UC33.1 - Modifica nome modello

[REQUIREMENT]
UID: UC33.1.1
TITLE: UC33.1.1 - Errore modifica nome modello

[REQUIREMENT]
UID: UC34
TITLE: UC34 - Avvia modifica modello

[REQUIREMENT]
UID: UC35
TITLE: UC35 - Salva modifica modello

[REQUIREMENT]
UID: UC35.1
TITLE: UC35.1 - Errore struttura non valida per il salvataggio

[REQUIREMENT]
UID: UC36
TITLE: UC36 - Scarta modifica modello

[REQUIREMENT]
UID: UC37
TITLE: UC37 - Elimina modello

[REQUIREMENT]
UID: UC38
TITLE: UC38 - Visualizza dettaglio requisito modello

[REQUIREMENT]
UID: UC38.1
TITLE: UC38.1 - Visualizza anagrafica requisito modello

[REQUIREMENT]
UID: UC38.1.1
TITLE: UC38.1.1 - Visualizza codice requisito modello

[REQUIREMENT]
UID: UC38.1.2
TITLE: UC38.1.2 - Visualizza nome del requisito modello

[REQUIREMENT]
UID: UC38.1.3
TITLE: UC38.1.3 - Visualizza descrizione modello

[REQUIREMENT]
UID: UC38.2
TITLE: UC38.2 - Visualizza lista dipendenze

[REQUIREMENT]
UID: UC38.2.1
TITLE: UC38.2.1 - Visualizza codice dipendenze

[REQUIREMENT]
UID: UC38.3
TITLE: UC38.3 - Visualizza lista non dipendenze

[REQUIREMENT]
UID: UC38.3.1
TITLE: UC38.3.1 - Visualizza codice non dipendenze

[REQUIREMENT]
UID: UC38.4
TITLE: UC38.4 - Visualizza decision tree requisito modello

[REQUIREMENT]
UID: UC38.4.1
TITLE: UC38.4.1 - Visualizza nodo decision tree modello

[REQUIREMENT]
UID: UC38.4.1.1
TITLE: UC38.4.1.1 - Visualizza nodo decisione modello

[REQUIREMENT]
UID: UC38.4.1.1.1
TITLE: UC38.4.1.1.1 - Visualizza codice requisito padre modello

[REQUIREMENT]
UID: UC38.4.1.1.2
TITLE: UC38.4.1.1.2 - Visualizza codice nodo modello

[REQUIREMENT]
UID: UC39
TITLE: UC39 - Visualizza dettaglio nodo modello decision tree

[REQUIREMENT]
UID: UC39.1
TITLE: UC39.1 - Visualizza dettaglio nodo decisione modello

[REQUIREMENT]
UID: UC39.1.1
TITLE: UC39.1.1 - Visualizza dettaglio codice requisito padre modello

[REQUIREMENT]
UID: UC39.1.2
TITLE: UC39.1.2 - Visualizza dettaglio codice nodo modello

[REQUIREMENT]
UID: UC39.1.3
TITLE: UC39.1.3 - Visualizza dettaglio domanda nodo modello

[REQUIREMENT]
UID: UC39.2
TITLE: UC39.2 - Visualizza dettaglio nodo foglia modello

[REQUIREMENT]
UID: UC40
TITLE: UC40 - Aggiungi requisito

[REQUIREMENT]
UID: UC40.1
TITLE: UC40.1 - Inserisci codice requisito

[REQUIREMENT]
UID: UC40.1.1
TITLE: UC40.1.1 - Errore codice requisito lunghezza non valida

[REQUIREMENT]
UID: UC40.1.2
TITLE: UC40.1.2 - Errore codice requisito duplicato

[REQUIREMENT]
UID: UC40.2
TITLE: UC40.2 - Inserisci nome requisito

[REQUIREMENT]
UID: UC40.2.1
TITLE: UC40.2.1 - Errore nome requisito non valido

[REQUIREMENT]
UID: UC40.3
TITLE: UC40.3 - Inserisci descrizione requisito

[REQUIREMENT]
UID: UC41
TITLE: UC41 - Elimina requisito

[REQUIREMENT]
UID: UC42
TITLE: UC42 - Modifica anagrafica requisito

[REQUIREMENT]
UID: UC42.1
TITLE: UC42.1 - Modifica codice requisito

[REQUIREMENT]
UID: UC42.1.1
TITLE: UC42.1.1 - Errore modifica codice requisito lunghezza non valida

[REQUIREMENT]
UID: UC42.1.2
TITLE: UC42.1.2 - Errore modifica codice requisito duplicato

[REQUIREMENT]
UID: UC42.2
TITLE: UC42.2 - Modifica nome requisito

[REQUIREMENT]
UID: UC42.2.1
TITLE: UC42.2.1 - Errore modifica nome requisito non valido

[REQUIREMENT]
UID: UC42.3
TITLE: UC42.3 - Modifica descrizione requisito

[REQUIREMENT]
UID: UC43
TITLE: UC43 - Aggiungi dipendenza

[REQUIREMENT]
UID: UC43.1
TITLE: UC43.1 - Errore dipendenza circolare

[REQUIREMENT]
UID: UC43.1.1
TITLE: UC43.1.1 - Visualizza grafo dipendenze

[REQUIREMENT]
UID: UC44
TITLE: UC44 - Rimuovi dipendenza

[REQUIREMENT]
UID: UC45
TITLE: UC45 - Aggiungi nodo figlio

[REQUIREMENT]
UID: UC45.1
TITLE: UC45.1 - Aggiungi nodo figlio sinistro

[REQUIREMENT]
UID: UC45.2
TITLE: UC45.2 - Aggiungi nodo figlio destro

[REQUIREMENT]
UID: UC46
TITLE: UC46 - Aggiungi nodo

[REQUIREMENT]
UID: UC46.1
TITLE: UC46.1 - Aggiungi nodo foglia

[REQUIREMENT]
UID: UC46.1.1
TITLE: UC46.1.1 - Aggiungi nodo PASS

[REQUIREMENT]
UID: UC46.1.2
TITLE: UC46.1.2 - Aggiungi nodo FAIL

[REQUIREMENT]
UID: UC46.1.3
TITLE: UC46.1.3 - Aggiungi nodo NA

[REQUIREMENT]
UID: UC46.2
TITLE: UC46.2 - Aggiungi nodo di decisione

[REQUIREMENT]
UID: UC46.2.1
TITLE: UC46.2.1 - Inserisci codice nodo decision tree

[REQUIREMENT]
UID: UC46.2.1.1
TITLE: UC46.2.1.1 - Errore codice nodo non valido

[REQUIREMENT]
UID: UC46.2.1.2
TITLE: UC46.2.1.2 - Errore codice nodo già esistente

[REQUIREMENT]
UID: UC46.2.2
TITLE: UC46.2.2 - Inserisci domanda nodo decision tree

[REQUIREMENT]
UID: UC46.2.2.1
TITLE: UC46.2.2.1 - Errore domanda vuota

[REQUIREMENT]
UID: UC47
TITLE: UC47 - Modifica nodo

[REQUIREMENT]
UID: UC47.1
TITLE: UC47.1 - Modifica codice nodo decision tree

[REQUIREMENT]
UID: UC47.1.1
TITLE: UC47.1.1 - Errore modifica codice nodo non valido

[REQUIREMENT]
UID: UC47.1.2
TITLE: UC47.1.2 - Errore modifica codice nodo già esistente

[REQUIREMENT]
UID: UC47.2
TITLE: UC47.2 - Modifica domanda nodo decision tree

[REQUIREMENT]
UID: UC47.2.1
TITLE: UC47.2.1 - Errore modifica domanda vuota

[REQUIREMENT]
UID: UC48
TITLE: UC48 - Rimuovi nodo

[REQUIREMENT]
UID: UC49
TITLE: UC49 - Errore nodo root

[REQUIREMENT]
UID: UC50
TITLE: UC50 - Esporta modello

[REQUIREMENT]
UID: UC50.1
TITLE: UC50.1 - Esporta modello in XML

[REQUIREMENT]
UID: UC50.2
TITLE: UC50.2 - Esporta modello in JSON
